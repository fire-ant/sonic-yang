module sonic-types {

    yang-version 1.1;

    namespace "http://github.com/Azure/sonic-head";
    prefix sonic-types;

    description "SONiC type for yang Models of SONiC OS";
    /*
     * Try to define only sonic specific types here. Rest can be written in
     * respective YANG files.
     */

    revision 2019-07-01 {
        description "First Revision";
    }

    typedef ip-family {
        type enumeration {
            enum IPv4;
            enum IPv6;
        }
    }

    typedef sonic-ip4-prefix {
        type string {
            pattern
             '(([0-9]|[1-9][0-9]|1[0-9][0-9]|2[0-4][0-9]|25[0-5])\.){3}'
            +  '([0-9]|[1-9][0-9]|1[0-9][0-9]|2[0-4][0-9]|25[0-5])'
            + '/(([0-9])|([1-2][0-9])|(3[0-2]))';
        }
    }

    typedef sonic-ip6-prefix {
        type string {
            pattern '((:|[0-9a-fA-F]{0,4}):)([0-9a-fA-F]{0,4}:){0,5}'
                 + '((([0-9a-fA-F]{0,4}:)?(:|[0-9a-fA-F]{0,4}))|'
                 + '(((25[0-5]|2[0-4][0-9]|[01]?[0-9]?[0-9])\.){3}'
                 + '(25[0-5]|2[0-4][0-9]|[01]?[0-9]?[0-9])))'
                 + '(/(([0-9])|([0-9]{2})|(1[0-1][0-9])|(12[0-8])))';
            pattern '(([^:]+:){6}(([^:]+:[^:]+)|(.*\..*)))|'
                 + '((([^:]+:)*[^:]+)?::(([^:]+:)*[^:]+)?)'
                 + '(/.+)';
        }
    }

    typedef sonic-ip-prefix {
      type union {
        type sonic-ip4-prefix;
        type sonic-ip6-prefix;
      }
    }

    typedef admin_status {
        type enumeration {
            enum up;
            enum down;
        }
    }

    typedef packet_action{
        type enumeration {
            enum DROP;
            enum ACCEPT;
            enum FORWARD;
            enum REDIRECT;
            enum DO_NOT_NAT;
        }
    }

    typedef ip_type {
        type enumeration {
            enum ANY;
            enum IP;
            enum NON_IP;
            enum IPV4;
            enum IPV6;
            enum IPv4ANY;
            enum NON_IP4;
            enum IPv6ANY;
            enum NON_IPv6;
            enum ARP;
        }
    }

    typedef acl_table_type {
        type enumeration {
            enum L2;
            enum L3;
            enum L3V6;
            enum MIRROR;
            enum MIRRORV6;
            enum MIRROR_DSCP;
            enum CTRLPLANE;
        }
    }

    typedef hwsku {
        type string {
            length 1..255;
            /* Should we list all hwsku here */
        }
    }

    typedef vlan_tagging_mode {
        type enumeration {
            enum tagged;
            enum untagged;
            enum priority_tagged;
        }
    }

    typedef crm_threshold_type {
        type string {
            length 1..64;
            pattern "percentage|used|free|PERCENTAGE|USED|FREE";
        }
    }

    typedef admin_mode {
        type enumeration {
            enum enabled;
            enum disabled;
        }
    }

    typedef ip-protocol-type {
        type enumeration {
            enum TCP;
            enum UDP;
        }
    }

    typedef interface_type {
        type enumeration {
            enum CR;
            enum CR2;
            enum CR4;
            enum SR;
            enum SR2;
            enum SR4;
            enum LR;
            enum LR4;
            enum KR;
            enum KR4;
            enum CAUI;
            enum GMII;
            enum SFI;
            enum XLAUI;
            enum KR2;
            enum CAUI4;
            enum XAUI;
            enum XFI;
            enum XGMII;
            enum none;
        }
    }

    typedef oper-status {
        type enumeration {
            enum unknown;
            enum up;
            enum down;
        }
        description "Operational status of an entity such as Port, MCLAG etc";
    }

    typedef mode-status {
        type enumeration {
            enum enable;
            enum disable;
        }
        description
            "This type can be used where toggle functionality required.
            For ex. IPv6-link-local-only, Dhcp-replay-link-select, SNMP traps etc";
    }

    typedef dhcp-relay-policy-action {
        type enumeration {
            enum discard;
            enum append;
            enum replace;
        }
        description "DHCP relay policy action value";
    }

    typedef percentage {
        type uint8 {
            range "0..100";
        }
        description
            "Integer indicating a percentage value";
    }

    typedef tpid_type {
        type string {
            pattern "0x8100|0x9100|0x9200|0x88a8|0x88A8";
        }
    }

    typedef meter_type {
        type enumeration {
            enum packets;
            enum bytes;
        }
    }

    typedef policer_mode {
        type enumeration {
            enum sr_tcm;
            enum tr_tcm;
            enum storm;
        }
    }

    typedef policer_color_source {
        type enumeration {
	    enum aware;
	    enum blind;
        }
    }


    typedef policer_packet_action {
        type enumeration {
            enum drop;
            enum forward;
            enum copy;
            enum copy_cancel;
            enum trap;
            enum log;
            enum deny;
            enum transit;
        }
    }

    typedef boolean_type {
        type string {
            pattern "false|true|False|True";
        }
    }

    typedef mac-addr-and-mask {
        type string {
            pattern "[0-9a-fA-F]{2}(:[0-9a-fA-F]{2}){5}|[0-9a-fA-F]{2}(:[0-9a-fA-F]{2}){5}/[0-9a-fA-F]{2}(:[0-9a-fA-F]{2}){5}";
        }
    }

    typedef hostname {
        type string {
            length 1..63;
        }
    }
}
